# -*- coding: utf-8 -*-

# Macro Begin: /home/aditya/snap/freecad/common/open_brep_file.FCMacro +++++++++++++++++++++++++++++++++++++++++++++++++
import FreeCAD
import Part
import Mesh
import sys
import os
import json
if len(sys.argv) < 3:
   print('Error: No output path argument provided')
   sys.exit()

# Retrieve the path argument
path = sys.argv[2]
output_filename = sys.argv[3]
manifest_path = sys.argv[4] if len(sys.argv) > 4 else None

#print(type(path))
__objs__ = []

def export_objects(objs, out_path):
    print('This is the file to which we export', out_path)
    Mesh.export(objs, out_path)

try:
    if manifest_path and os.path.exists(manifest_path):
        print('Using manifest at', manifest_path)
        with open(manifest_path, 'r', encoding='utf-8') as mf:
            manifest = json.load(mf)
        # Create a fresh document to hold merged parts
        doc = FreeCAD.newDocument('MergedModel')
        for part in manifest.get('parts', []):
            brep_rel = part.get('brepPath')
            name = part.get('name') or 'Part'
            if not brep_rel:
                continue
            brep_abs = brep_rel
            if not os.path.isabs(brep_abs):
                brep_abs = os.path.join(os.getcwd(), brep_rel)
            print('Inserting part', name, 'from', brep_abs)
            # Insert the brep into current document
            Part.insert(brep_abs, doc.Name)
            if len(doc.Objects) > 0:
                obj = doc.Objects[-1]
                try:
                    obj.Label = name
                except Exception:
                    pass
                __objs__.append(obj)
        export_objects(__objs__, output_filename)
    else:
        print('The path of the brep file', path)
        Part.open(path)
        doc = FreeCAD.activeDocument()
        print(doc.Label)
        # Collect all meshable objects in the document
        for objz in doc.Objects:
            __objs__.append(objz)
        export_objects(__objs__, output_filename)
finally:
    del __objs__
